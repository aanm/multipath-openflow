module test-interface {
    yang-version 1;
    namespace "urn:ietf:params:xml:ns:yang:test-interface";
    prefix "sn";

    description
        "test file";   

    revision "2014-07-01" {
        description
            "Initial revision";
        reference "will be defined";
    }
    
    container interfaces {
    
        container block {
            
            leaf address {
                type string;
            }
            leaf location {
                type string;
            }
        }
    
        list interface {
            key "name";
         
            leaf name {
                type string;
            }
            leaf type {
                type string;
            }
            leaf enabled {
                type string;
            }
        }
    }
}
